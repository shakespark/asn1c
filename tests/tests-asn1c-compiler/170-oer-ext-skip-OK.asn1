-- OK: Everything is fine

-- iso.org.dod.internet.private.enterprise (1.3.6.1.4.1)
-- .spelio.software.asn1c.test (9363.1.5.1)
-- .170

-- OER forward compatibility with extension additions (issues #14, #15).
--
-- This module is the "v1" view of types whose "v2" peers carry extension
-- additions unknown to us.  A v1 decoder must skip the unknown extension
-- material and keep decoding the enclosing type, instead of silently
-- shifting subsequent fields (#14: oer_open_type_skip() used to skip only
-- the open type length determinant, not its contents) or failing the
-- whole PDU (#15: an unknown CHOICE extension alternative used to return
-- RC_FAIL).
--
-- Types in this module:
--   M/Inner: SEQUENCE with an extensible inner SEQUENCE.  The v2 peer is
--            Inner ::= SEQUENCE { x INTEGER(0..255), ..., y INTEGER(0..255) }
--            (and a v3 peer additionally has z INTEGER(0..255)).
--            Decoding v2/v3 bytes must recover a, x and b.
--   C:       extensible CHOICE; the v2 peer adds c2 INTEGER(0..255) after
--            the extension marker.  Decoding a v2 selection of c2 must
--            succeed with no alternative selected (C_PR_NOTHING).
--   MC:      C nested between two fields; proves that fields after an
--            unknown CHOICE alternative are still recovered.
--
-- The golden v2/v3 byte streams in check-170.-gen-OER.c were produced by
-- the OSS ASN.1 Tools v12.0 OER codec (the interoperability reference)
-- and cross-checked with asn1tools; the OSS v1 decoder gracefully skips
-- all of them, which is the behavior this fixture pins down for asn1c.

ModuleOerExtSkip
	{ iso org(3) dod(6) internet (1) private(4) enterprise(1)
		spelio(9363) software(1) asn1c(5) test(1) 170 }
	DEFINITIONS AUTOMATIC TAGS ::=
BEGIN

	M ::= SEQUENCE {
		a INTEGER(0..255),
		inner Inner,
		b INTEGER(0..255)
	}

	Inner ::= SEQUENCE {
		x INTEGER(0..255),
		...
	}

	C ::= CHOICE {
		c1 INTEGER(0..255),
		...
	}

	MC ::= SEQUENCE {
		pre INTEGER(0..255),
		c C,
		post INTEGER(0..255)
	}

END
